FME workspace wind_farm_share.fmw

Parameters:
- SourceDataset_POSTGIS_4 = Local   # Connection
- SourceDataset_POSTGIS_2 = qa_database   # Connection
- SourceDataset_POSTGIS_11 = qa_database   # Connection
- SourceDataset_ARCGISFEATURES_38 = https://environment.data.gov.uk/arcgis/rest/services/DEFRA/RailNoiseLAeq16hRound3/FeatureServer   # Host
- DestDataset_POSTGIS_29 = qa_database   # Connection
- SourceDataset_ARCGISFEATURES_40 = https://environment.data.gov.uk/arcgis/rest/services/DEFRA/RailNoiseLnightRound3/FeatureServer   # Host
- DestDataset_POSTGIS_6 = qa_database   # Connection
- SourceDataset_FILEGDB_5 = D:\Project\adding_new_data\DEFRA_RoadNoiseLnightRound3_FGDB_Full\data.gdb   # File Geodatabase
- DestDataset_POSTGIS_26 = qa_database   # Connection
- SourceDataset_FILEGDB_4 = D:\Project\adding_new_data\DEFRA_RoadNoiseLAeq16hRound3_FGDB_Full\data.gdb   # File Geodatabase
- SourceDataset_CSV2_6 = https://chargepoints.dft.gov.uk/api/retrieve/registry/format/csv   # Source CSV (Comma Separated Value) File(s)
- DestDataset_POSTGIS_13 = qa_database   # Connection

Readers:
- POSTGIS_6: POSTGIS from $(SourceDataset_POSTGIS_4) in EPSG:27700
- POSTGIS_7: POSTGIS from $(SourceDataset_POSTGIS_2) in EPSG:27700
- POSTGIS_14: POSTGIS from $(SourceDataset_POSTGIS_11) in EPSG:27700
- ARCGISFEATURES_20: ARCGISFEATURES from $(SourceDataset_ARCGISFEATURES_38)
- ARCGISFEATURES_21: ARCGISFEATURES from $(SourceDataset_ARCGISFEATURES_40) in EPSG:27700
- FILEGDB_2: FILEGDB from $(SourceDataset_FILEGDB_5) in EPSG:27700
- FILEGDB_3: FILEGDB from $(SourceDataset_FILEGDB_4) in EPSG:27700
- CSV2_4: CSV2 from $(SourceDataset_CSV2_6) in LL-WGS84

Writers:
- POSTGIS_19: POSTGIS to $(DestDataset_POSTGIS_29)
- POSTGIS_5: POSTGIS to $(DestDataset_POSTGIS_6)
- POSTGIS_21: POSTGIS to $(DestDataset_POSTGIS_26) in EPSG:27700
- POSTGIS_10: POSTGIS to $(DestDataset_POSTGIS_13) in EPSG:27700

CSV (reader CSV2_4)
    attributes: chargeDeviceID varchar(33), reference varchar(19), name varchar(78), latitude y_coordinate, longitude x_coordinate, subBuildingName varchar(31), buildingName varchar(33), buildingNumber varchar(58), thoroughfare varchar(62), street varchar(87), doubleDependantLocality varchar(36), dependantLocality varchar(33), town varchar(31), county varchar(41), postcode varchar(10), countryCode varchar(3), uprn varchar(1), deviceDescription varchar(227), locationShortDescription varchar(163), locationLongDescription varchar(432), deviceManufacturer varchar(14), deviceModel varchar(92), deviceOwnerName varchar(44), deviceOwnerWebsite varchar(70), deviceOwnerTelephoneNo varchar(19), deviceOwnerContactName varchar(1), deviceControllerName varchar(39), deviceControllerWebsite varchar(46), deviceControllerTelephoneNo varchar(20), deviceControllerContactName varchar(1),
      deviceNetworks varchar(47), chargeDeviceStatus varchar(15), publishStatus varchar(10), deviceValidated uint32, dateCreated varchar(20), dateUpdated varchar(20), moderated varchar(2), lastUpdated datetime, lastUpdatedBy varchar(44), attribution varchar(39), dateDeleted varchar(4), paymentRequired uint32, paymentRequiredDetails varchar(125), subscriptionRequired uint32, subscriptionRequiredDetails varchar(125), parkingFeesFlag uint32, parkingFeesDetails varchar(125), parkingFeesUrl varchar(80), accessRestrictionFlag uint32, accessRestrictionDetails varchar(522), physicalRestrictionFlag uint32, physicalRestrictionText varchar(73), onStreetFlag uint32, locationType varchar(26), bearing varchar(3), access24Hours uint32, accessMondayFrom varchar(6), accessMondayTo varchar(6), accessTuesdayFrom varchar(6), accessTuesdayTo varchar(6),
      accessWednesdayFrom varchar(6), accessWednesdayTo varchar(6), accessThursdayFrom varchar(6), accessThursdayTo varchar(6), accessFridayFrom varchar(6), accessFridayTo varchar(6), accessSaturdayFrom varchar(6), accessSaturdayTo varchar(6), accessSundayFrom varchar(6), accessSundayTo varchar(6), connector1ID uint32, connector1Type varchar(28), connector1RatedOutputKW real32, connector1OutputCurrent uint32, connector1RatedVoltage uint32, connector1ChargeMethod varchar(16), connector1ChargeMode uint32, connector1TetheredCable uint32, connector1Status varchar(15), connector1Description varchar(81), connector1Validated uint32, connector2ID uint32, connector2Type varchar(28), connector2RatedOutputKW real32, connector2OutputCurrent uint32, connector2RatedVoltage uint32, connector2ChargeMethod varchar(16), connector2ChargeMode uint32, connector2TetheredCable uint32, connector2Status varchar(15),
      connector2Description varchar(81), connector2Validated uint32, connector3ID uint32, connector3Type varchar(28), connector3RatedOutputKW real32, connector3OutputCurrent uint32, connector3RatedVoltage uint32, connector3ChargeMethod varchar(16), connector3ChargeMode uint32, connector3TetheredCable uint32, connector3Status varchar(15), connector3Description varchar(64), connector3Validated uint32, connector4ID uint32, connector4Type varchar(28), connector4RatedOutputKW real32, connector4OutputCurrent uint32, connector4RatedVoltage uint32, connector4ChargeMethod varchar(16), connector4ChargeMode uint32, connector4TetheredCable uint32, connector4Status varchar(15), connector4Description varchar(1), connector4Validated uint32, connector5ID uint32, connector5Type varchar(28), connector5RatedOutputKW real32, connector5OutputCurrent uint32, connector5RatedVoltage uint32, connector5ChargeMethod varchar(16),
      connector5ChargeMode uint32, connector5TetheredCable uint32, connector5Status varchar(11), connector5Description varchar(1), connector5Validated uint32, connector6ID uint32, connector6Type varchar(27), connector6RatedOutputKW real32, connector6OutputCurrent uint32, connector6RatedVoltage uint32, connector6ChargeMethod varchar(16), connector6ChargeMode uint32, connector6TetheredCable uint32, connector6Status varchar(11), connector6Description varchar(1), connector6Validated uint32, connector7ID uint32, connector7Type varchar(27), connector7RatedOutputKW real32, connector7OutputCurrent uint32, connector7RatedVoltage uint32, connector7ChargeMethod varchar(15), connector7ChargeMode uint32, connector7TetheredCable uint32, connector7Status varchar(11), connector7Description varchar(1), connector7Validated uint32, connector8ID varchar(1), connector8Type varchar(1), connector8RatedOutputKW varchar(1),
      connector8OutputCurrent varchar(1), connector8RatedVoltage varchar(1), connector8ChargeMethod varchar(1), connector8ChargeMode varchar(1), connector8TetheredCable varchar(1), connector8Status varchar(1), connector8Description varchar(1), connector8Validated varchar(1)
    -> DuplicateFilter_6
DuplicateFilter_6
    INPUT_ORDERED_CHOICE = No
    KEYATTR = chargeDeviceID
    UNIQUE -> lyr_national_charge_point_registry (writer POSTGIS_10)
Note: postcode is varchar 9 as it has space at the end , there are null values in the boolean column so they are stored as int
lyr_national_charge_point_registry (writer POSTGIS_10)
    attributes: id varchar(33),PrimaryKey, reference varchar(30), name varchar(78), latitude float8, longitude float8, sub_building_name varchar(30), buildingname varchar(80), buildingnumber varchar(57), thoroughfare varchar(80), street varchar(101), double_dependant_locality varchar(35), dependant_locality varchar(35), town varchar(30), county varchar(40), postcode varchar(9), countrycode varchar(2), uprn int8, devicedescription varchar(226), locationshortdescription varchar(162), locationlongdescription varchar(431), devicemanufacturer varchar(21), devicemodel varchar(91), deviceownername varchar(44), deviceownerwebsite varchar(75), deviceownertelephoneno varchar(19), deviceownercontactname varchar(1), devicecontrollername varchar(38), devicecontrollerwebsite varchar(74), devicecontrollertelephoneno varchar(20), devicecontrollercontactname varchar(1),
      devicenetworks varchar(59), chargedevicestatus varchar(15), publishstatus varchar(10), devicevalidated int8, datecreated varchar(20), dateupdated varchar(20), moderated bool, lastupdated timestamp, lastupdatedby varchar(43), attribution varchar(42), datedeleted varchar(4), paymentrequired int8, paymentrequireddetails varchar(161), subscriptionrequired int8, subscriptionrequireddetails varchar(161), parkingfeesflag int8, parkingfeesdetails varchar(183), parkingfeesurl varchar(161), accessrestrictionflag int8, accessrestrictiondetails text, physicalrestrictionflag int8, physicalrestrictiontext varchar(76), onstreetflag int8, locationtype varchar(26), bearing varchar(3), access24hours int8, accessmondayfrom varchar(6), accessmondayto varchar(6), accesstuesdayfrom varchar(6), accesstuesdayto varchar(6),
      accesswednesdayfrom varchar(6), accesswednesdayto varchar(6), accessthursdayfrom varchar(6), accessthursdayto varchar(6), accessfridayfrom varchar(6), accessfridayto varchar(6), accesssaturdayfrom varchar(6), accesssaturdayto varchar(6), accesssundayfrom varchar(6), accesssundayto varchar(6), connector1id int4, connector1type varchar(28), connector1ratedoutputkw float4, connector1outputcurrent int2, connector1ratedvoltage int2, connector1chargemethod varchar(16), connector1chargemode int2, connector1tetheredcable int2, connector1status varchar(15), connector1description varchar(82), connector1validated int2, connector2id int4, connector2type varchar(28), connector2ratedoutputkw float4, connector2outputcurrent int2, connector2ratedvoltage int2, connector2chargemethod varchar(16), connector2chargemode int2, connector2tetheredcable int2, connector2status varchar(15),
      connector2description varchar(85), connector2validated int2, connector3id int4, connector3type varchar(28), connector3ratedoutputkw float4, connector3outputcurrent int2, connector3ratedvoltage int2, connector3chargemethod varchar(16), connector3chargemode int2, connector3tetheredcable int2, connector3status varchar(15), connector3description varchar(85), connector3validated int2, connector4id int4, connector4type varchar(28), connector4ratedoutputkw float4, connector4outputcurrent int2, connector4ratedvoltage int2, connector4chargemethod varchar(16), connector4chargemode int2, connector4tetheredcable int2, connector4status varchar(15), connector4description varchar(85), connector4validated int2, connector5id int4, connector5type varchar(28), connector5ratedoutputkw float4, connector5outputcurrent int2, connector5ratedvoltage int2, connector5chargemethod varchar(16),
      connector5chargemode int2, connector5tetheredcable int2, connector5status varchar(15), connector5description varchar(85), connector5validated int2, connector6id int4, connector6type varchar(28), connector6ratedoutputkw float4, connector6outputcurrent int2, connector6ratedvoltage int2, connector6chargemethod varchar(16), connector6chargemode int2, connector6tetheredcable int2, connector6status varchar(15), connector6description varchar(85), connector6validated int2, connector7id int4, connector7type varchar(28), connector7ratedoutputkw float4, connector7outputcurrent int2, connector7ratedvoltage int2, connector7chargemethod varchar(16), connector7chargemode int2, connector7tetheredcable int2, connector7status varchar(15), connector7description varchar(85), connector7validated int2, connector8id int4, connector8type varchar(28), connector8ratedoutputkw float4,
      connector8outputcurrent int2, connector8ratedvoltage int2, connector8chargemethod varchar(16), connector8chargemode int2, connector8tetheredcable int2, connector8status varchar(15), connector8description varchar(85), connector8validated int2, last_update timestamp

Bookmark: Noise
Rail_Noise_LAeq16h_England_Round_3 (reader ARCGISFEATURES_20)
    attributes: objectid OID, noiseclass String(11)
    -> DuplicateFilter_7
DuplicateFilter_7
    INPUT_ORDERED_CHOICE = No
    KEYATTR = objectid
    UNIQUE -> lyr_rail_noise_day (writer POSTGIS_19)
lyr_rail_noise_day (writer POSTGIS_19)
    attributes: id text,PrimaryKey, noiseclass varchar(11), last_update timestamp
Rail_Noise_Lnight_England_Round_3 (reader ARCGISFEATURES_21)
    attributes: objectid OID, noiseclass String(11)
    -> DuplicateFilter_8
DuplicateFilter_8
    INPUT_ORDERED_CHOICE = No
    KEYATTR = objectid
    UNIQUE -> lyr_rail_noise_night (writer POSTGIS_5)
lyr_rail_noise_night (writer POSTGIS_5)
    attributes: id int4,PrimaryKey, noiseclass varchar(11), last_update timestamp
Road_Noise_Lnight_England_Round_3 (reader FILEGDB_2)
    attributes: OBJECTID objectid, noiseclass text(11), Shape_Length double, Shape_Area double
    -> DuplicateFilter_9
DuplicateFilter_9
    INPUT_ORDERED_CHOICE = No
    KEYATTR = OBJECTID
    UNIQUE -> lyr_road_noise_night (writer POSTGIS_21)
lyr_road_noise_night (writer POSTGIS_21)
    attributes: id int4,PrimaryKey, noiseclass varchar(11), shape_length float8, shape_area float8
Road_Noise_LAeq16h_England_Round_3 (reader FILEGDB_3)
    attributes: OBJECTID objectid, noiseclass text(11), Shape_Length double, Shape_Area double
    -> DuplicateFilter_10
DuplicateFilter_10
    INPUT_ORDERED_CHOICE = No
    KEYATTR = OBJECTID
    UNIQUE -> lyr_road_noise_day (writer POSTGIS_21)
lyr_road_noise_day (writer POSTGIS_21)
    attributes: id int4,PrimaryKey, noiseclass varchar(11), shape_length float8, shape_area float8
